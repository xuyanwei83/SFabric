module fabric-address-tracker {
  yang-version 1;
  namespace "urn:opendaylight:fabric:address-tracker";
  prefix fabric-address-tracker;

  import ietf-yang-types {
    prefix yang;
    revision-date 2010-09-24;
  }
  import opendaylight-inventory {
    prefix inv;
    revision-date 2013-08-19;
  }

  organization "Cisco Systems Inc";
  contact
    "Alex Fan <alefan@cisco.com>";
  description
    "YANG version of the  Fabric Address Tracker Data Model";

  revision 2014-04-02 {
    description
      "Fabric Address Tracker module draft.";
  }

  grouping fabric-address {
    leaf mac {
        type yang:mac-address;
        mandatory true;
        description
          "the mac address of the host.";
    }
    leaf node-connector-ref {
      type inv:node-connector-ref;
    }
  }

  container fabric-addresses {
    config false;
    list fabric-address {
      key "mac";
      uses fabric-address;
    }
  }
}
